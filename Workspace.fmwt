FME workspace Workspace.fmwt
Title: Workspace
Description: Printing the orientation of a specific feature layer based on bound ratios.

Parameters:
- SourceDataset_SPATIALITE = $(FME_MF_DIR)Data/LGALayer.sqlite   # SpatiaLite Database
- DestDataset_SPATIALITE = $(FME_MF_DIR)Data\LGALayer.sqlite   # SpatiaLite Database

Readers:
- SPATIALITE_1: SPATIALITE from $(SourceDataset_SPATIALITE)

Writers:
- SPATIALITE_2: SPATIALITE to $(DestDataset_SPATIALITE)

Bookmark: Calculate Map Orientation for Feature layers
admin_lga (reader SPATIALITE_1)
    attributes: lgacode string(10), lganame string(50), statecode string(10), statename string(25)
    -> BoundsExtractor
Note: Extracts the bounds of the / features in the layer.
BoundsExtractor
    YMIN = ymin
    XMAX = xmax
    YMAX = ymax
    XMIN = xmin
    -> Calculate_Bound_Ratios
Note: Calculate Bound Ratios
Calculate_Bound_Ratios: AttributeCreator
    ATTR_TABLE:
      SET_TO diff_x = @min(@Value(xmax),@Value(xmin))
      SET_TO diff_y = @min(@Value(ymax),@Value(ymin))
      SET_TO ratio = @div(@Value(diff_x),@Value(diff_y))
    -> Tester
Note: Tests if ratio > 1
Tester
    BOOL_OP = OR
    TEST_MODE = Automatic
    TEST_CLAUSE = TEST @Value(ratio) > 1
    TEST_DESCRIPTION = ""
    PASSED -> Portrait
    FAILED -> Landscape
Note: Combine the two different layers
Merger_Layer: FeatureHolder
    -> AttributeKeeper
Note: Remove redundant felds
AttributeKeeper
    KEEP_ATTRS = lgacode,lganame,orientation,statecode,ratio,statename
    -> layers_with_orentation (writer SPATIALITE_2)
layers_with_orentation (writer SPATIALITE_2)
    attributes: lgacode string(10), lganame string(50), statecode string(10), statename string(25), ratio real64, orientation string(200)

Bookmark: Defines category Port/Landsape
Portrait: AttributeCreator
    ATTR_TABLE = SET_TO orientation = Portrait
    -> Merger_Layer
Landscape: AttributeCreator
    ATTR_TABLE = SET_TO orientation = Landscape
    -> Merger_Layer
